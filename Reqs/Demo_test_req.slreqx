# Demo_test_req

## #1: Number of Traffic Lights (Functional)
The number of traffic lights in the scenario is 1

## #2: Number of stop signs (Functional)
The number of stop signs in the scenario is 1
